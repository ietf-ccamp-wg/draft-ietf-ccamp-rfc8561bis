module ietf-microwave-types {
  yang-version 1.1;
  namespace "urn:ietf:params:xml:ns:yang:ietf-microwave-types";
  prefix mw-types;

  organization
    "Internet Engineering Task Force (IETF) CCAMP WG";
  contact
    "WG List: <mailto:ccamp@ietf.org>

     Editors:
      Jonas Ahlberg (jonas.ahlberg@ericsson.com)
      Min Ye (amy.yemin@huawei.com)
      Xi Li (Xi.Li@neclab.eu)
      Daniela Spreafico (daniela.spreafico@nokia.com)
      Marko Vaupotic (Marko.Vaupotic@aviatnet.com)
      Danilo Pala (danilo.pala@techmahindra.com)";
  description
    "This is a YANG module for the entities in
     a generic interface protection mechanism.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC 8561bis;
     see the RFC itself for full legal notices.";

  // RFC Ed.: replace 8561bis with actual RFC number and remove
  // this note
  // replace the revision date with the module publication date
  // the format is (year-month-day)

  revision 2026-10-29 {
    description
      "TBD";
    reference
      "RFC XXXX: A YANG Data Model for Microwave Radio Link";
  }
  revision 2019-06-19 {
    description
      "Initial revision.";
    reference
      "RFC 8561: A YANG Data Model for Microwave Radio Link";
  }

  /*
   * Radio-link-terminal mode identities
   */

  identity rlt-mode {
    status deprecated;
    description
      "A description of the mode in which the radio link
       terminal is configured.  The format is X plus Y.
       X represents the number of bonded carrier terminations.
       Y represents the number of protecting carrier
       terminations.";
  }

  identity one-plus-zero {
    base rlt-mode;
    status deprecated;
    description
      "1 carrier termination only.";
  }

  identity one-plus-one {
    base rlt-mode;
    status deprecated;
    description
      "1 carrier termination
       and 1 protecting carrier termination.";
  }

  identity two-plus-zero {
    base rlt-mode;
    status deprecated;
    description
      "2 bonded carrier terminations.";
  }

  /*
   * Coding and modulation identities
   */

  identity coding-modulation {
    description
      "The coding and modulation schemes.";
  }

  identity fourth-bpsk {
    base coding-modulation;
    description
      "Fourth BPSK coding and modulation scheme.";
  }

  identity half-bpsk {
    base coding-modulation;
    description
      "Half BPSK coding and modulation scheme.";
  }

  identity half-bpsk-strong {
    base half-bpsk;
    description
      "Half BPSK strong coding and modulation scheme.";
  }

  identity half-bpsk-light {
    base half-bpsk;
    description
      "Half BPSK light coding and modulation scheme.";
  }

  identity bpsk {
    base coding-modulation;
    description
      "BPSK coding and modulation scheme.";
  }

  identity bpsk-strong {
    base bpsk;
    description
      "BPSK strong coding and modulation scheme.";
  }

  identity bpsk-light {
    base bpsk;
    description
      "BPSK light coding and modulation scheme.";
  }

  identity qpsk {
    base coding-modulation;
    description
      "QPSK coding and modulation scheme.";
  }

  identity psk-8 {
    base coding-modulation;
    description
      "8PSK coding and modulation scheme.";
  }

  identity qam-4 {
    base coding-modulation;
    description
      "4 QAM coding and modulation scheme.";
  }

  identity qam-4-strong {
    base qam-4;
    description
      "4 QAM strong coding and modulation scheme.";
  }

  identity qam-4-light {
    base qam-4;
    description
      "4 QAM light coding and modulation scheme.";
  }

  identity qam-16 {
    base coding-modulation;
    description
      "16 QAM coding and modulation scheme.";
  }

  identity qam-16-strong {
    base qam-16;
    description
      "16 QAM strong coding and modulation scheme.";
  }

  identity qam-16-light {
    base qam-16;
    description
      "16 QAM light coding and modulation scheme.";
  }

  identity qam-32 {
    base coding-modulation;
    description
      "32 QAM coding and modulation scheme.";
  }

  identity qam-32-strong {
    base qam-32;
    description
      "32 QAM strong coding and modulation scheme.";
  }

  identity qam-32-light {
    base qam-32;
    description
      "32 QAM light coding and modulation scheme.";
  }

  identity qam-64 {
    base coding-modulation;
    description
      "64 QAM coding and modulation scheme.";
  }

  identity qam-64-strong {
    base qam-64;
    description
      "64 QAM strong coding and modulation scheme.";
  }

  identity qam-64-light {
    base qam-64;
    description
      "64 QAM light coding and modulation scheme.";
  }

  identity qam-128 {
    base coding-modulation;
    description
      "128 QAM coding and modulation scheme.";
  }

  identity qam-128-strong {
    base qam-128;
    description
      "128 QAM strong coding and modulation scheme.";
  }

  identity qam-128-light {
    base qam-128;
    description
      "128 QAM light coding and modulation scheme.";
  }

  identity qam-256 {
    base coding-modulation;
    description
      "256 QAM coding and modulation scheme.";
  }

  identity qam-256-strong {
    base qam-256;
    description
      "256 QAM strong coding and modulation scheme.";
  }

  identity qam-256-light {
    base qam-256;
    description
      "256 QAM light coding and modulation scheme.";
  }

  identity qam-512 {
    base coding-modulation;
    description
      "512 QAM coding and modulation scheme.";
  }

  identity qam-512-strong {
    base qam-512;
    description
      "512 QAM strong coding and modulation scheme.";
  }

  identity qam-512-light {
    base qam-512;
    description
      "512 QAM light coding and modulation scheme.";
  }

  identity qam-1024 {
    base coding-modulation;
    description
      "1024 QAM coding and modulation scheme.";
  }

  identity qam-1024-strong {
    base qam-1024;
    description
      "1024 QAM strong coding and modulation scheme.";
  }

  identity qam-1024-light {
    base qam-1024;
    description
      "1024 QAM light coding and modulation scheme.";
  }

  identity qam-2048 {
    base coding-modulation;
    description
      "2048 QAM coding and modulation scheme.";
  }

  identity qam-2048-strong {
    base qam-2048;
    description
      "2048 QAM strong coding and modulation scheme.";
  }

  identity qam-2048-light {
    base qam-2048;
    description
      "2048 QAM light coding and modulation scheme.";
  }

  identity qam-4096 {
    base coding-modulation;
    description
      "4096 QAM coding and modulation scheme.";
  }

  identity qam-4096-strong {
    base qam-4096;
    description
      "4096 QAM strong coding and modulation scheme.";
  }

  identity qam-4096-light {
    base qam-4096;
    description
      "4096 QAM light coding and modulation scheme.";
  }

  /*
   * TDM-type identities
   */

  identity tdm-type {
    description
      "A description of the type of TDM connection,
       also indicating the supported capacity of the
       connection.";
  }

  identity E1 {
    base tdm-type;
    description
      "E1 connection, 2.048 Mbit/s.";
  }

  identity STM-1 {
    base tdm-type;
    description
      "STM-1 connection, 155.52 Mbit/s.";
  }

  typedef power {
    type decimal64 {
      fraction-digits 1;
    }
    description
      "Type used for the power values in the data nodes
       for configuration or status.";
  }

  /*
   * Radio-link-terminal mode grouping
   */

  grouping rlt-mode {
    description
      "This grouping provides a flexible definition of number
       of bonded carriers and protecting carriers of a radio
       link.";
    leaf num-bonded-carriers {
      type uint32;
      mandatory true;
      description
        "Number of bonded carriers.";
    }
    leaf num-protecting-carriers {
      type uint32;
      mandatory true;
      description
        "Number of protecting carriers.";
    }
  }

  /*
   * Common microwave properties ode grouping
   */

  grouping common-microwave-properties {
    description
      "This grouping provides a reusable set of microwave
       properties.";
    leaf tx-frequency {
      type uint32;
      units "kHz";
      mandatory true;
      description
        "Selected transmitter frequency.";
    }
    leaf actual-rx-frequency {
      type uint32;
      units "kHz";
      config false;
      description
        "Computed receiver frequency.";
    }
    leaf channel-separation {
      type uint32;
      units "kHz";
      mandatory true;
      description
        "The amount of bandwidth allocated to a carrier.  The
         distance between adjacent channels in a radio
         frequency channels arrangement";
      reference
        "ETSI EN 302 217-1";
    }
    leaf actual-transmitted-level {
      type power {
        range "-99..99";
      }
      units "dBm";
      config false;
      description
        "Actual transmitted power level (0.1 dBm resolution).";
      reference
        "ETSI EN 301 129";
    }
    leaf actual-tx-cm {
      type identityref {
        base mw-types:coding-modulation;
      }
      config false;
      description
        "Actual coding/modulation in transmitting direction.";
    }
    leaf actual-snir {
      type decimal64 {
        fraction-digits 1;
        range "0..99";
      }
      units "dB";
      config false;
      description
        "Actual signal to noise plus the interference ratio
         (0.1 dB resolution).";
    }
  }
}
